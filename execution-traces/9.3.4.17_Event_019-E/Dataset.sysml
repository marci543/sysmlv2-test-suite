package Event019E_Data {
	enum def TraceElement {
        enum S1_1_entry;
        enum S2_1_1_entry;
		enum T3_testEnd;
	}

	enum def Transition {
		enum T1;
		enum T2;
		enum T1_1;
		enum T1_2;
		enum T2_1;
		enum T2_1_1;
		enum T2_1_2;
		enum T2_2;
		enum T3;
	}
	
	enum def Event {
		enum in_ContinueSignal;
	}
}
